[DOCUMENT]
TITLE: CELL_WIDTH — Cell Width Measurement Tables
UID: REQ-CWM

[GRAMMAR]
ELEMENTS:
- TAG: REQUIREMENT
  FIELDS:
  - TITLE: UID
    TYPE: String
    REQUIRED: True
  - TITLE: STATUS
    TYPE: SingleChoice(Draft, Approved, In Progress, Implemented, Verified)
    REQUIRED: False
  - TITLE: PRIORITY
    TYPE: SingleChoice(Must, Should, Could, Wont)
    REQUIRED: False
  - TITLE: GITHUB
    TYPE: String
    REQUIRED: False
  - TITLE: TITLE
    TYPE: String
    REQUIRED: False
  - TITLE: STATEMENT
    TYPE: String
    REQUIRED: True
  - TITLE: COMMENT
    TYPE: String
    REQUIRED: False
  RELATIONS:
  - TYPE: Parent

[TEXT]
STATEMENT: >>>
This document specifies the functional requirements for Cell Width Measurement Tables
(feature id CELL_WIDTH). The feature provides a static, pure function Cell_Width that
returns the terminal column count (0, 1, or 2) for any Unicode scalar value, using
binary search over precomputed, version-tagged Unicode width tables bundled at compile
time.

This feature is complementary to the WCWIDTH feature (wcwidth.sdoc): whereas WCWIDTH
probes the POSIX C library wcwidth() function at runtime to discover the locale's
Unicode version, CELL_WIDTH provides a self-contained lookup independent of the OS
locale. The two approaches can be used together (prefer CELL_WIDTH for consistent
cross-platform results; use WCWIDTH to confirm locale coverage) or independently.

The width tables encode three categories of terminal column width:

  0  — combining / non-spacing characters (category M), control codes, and special
       codepoints that consume no columns (ZWJ U+200D, VS16 U+FE0F, etc.)
  1  — narrow characters: the standard width for ASCII, Latin script, most symbols
  2  — wide / fullwidth characters: CJK ideographs, fullwidth forms, some emoji

Multiple table versions are bundled (at minimum Unicode 3.0, 13.0, and 16.0) and
the active version is selected at startup by reading the UNICODE_VERSION environment
variable, defaulting to the latest bundled table when the variable is absent or
unrecognised.

The lookup function is a pure function with no I/O and no side effects, making it
eligible for Gold SPARK proof. The tables are declared as constant arrays (not
heap-allocated), ensuring O(1) space and O(log N) time per lookup via binary search
over sorted codepoint ranges.
<<<

[SECTION]
TITLE: Width Table Data

[REQUIREMENT]
UID: FUNC-CWM-001
STATUS: Approved
PRIORITY: Must
TITLE: Bundled Unicode Width Table Versions
STATEMENT: >>>
The library shall bundle precomputed Unicode width tables for at least the following
Unicode standard versions:

  Unicode 3.0   — baseline table covering the BMP blocks available in 1999;
                  includes Braille Patterns (U+2800..U+28FF) and all codepoints
                  assigned by Unicode 3.0.

  Unicode 13.0  — table updated to include the Symbols for Legacy Computing block
                  (U+1FB00..U+1FBFF) and all other codepoints assigned or reclassified
                  between Unicode 3.0 and 13.0.

  Unicode 16.0  — table updated to include the Symbols for Legacy Computing Supplement
                  (U+1CD00..U+1CDFB) and all other codepoints assigned or reclassified
                  between Unicode 13.0 and 16.0.

Each table shall be a constant (compile-time) data structure that maps contiguous
codepoint ranges to a Cell_Width value (0, 1, or 2). The tables shall be stored in
sorted order of codepoint range start value so that binary search can be applied
directly (FUNC-CWM-002).

Each bundled table shall be identified by a Table_Version discriminant value
(FUNC-CWM-003) so that the runtime version-selection logic (FUNC-CWM-004 and
FUNC-CWM-005) can index into the correct table without conditional branching in the
lookup path.

Adding support for a future Unicode version (e.g., 17.0) shall require only: (a)
generating the new table data, (b) extending the Table_Version enumeration, and (c)
updating the version-selection logic. No change to the binary search algorithm
(FUNC-CWM-002) or the public API (FUNC-CWM-010) shall be required.
<<<
COMMENT: >>>
The choice of Unicode 3.0, 13.0, and 16.0 as the minimum set mirrors the sentinel
codepoints used by the WCWIDTH feature (FUNC-WCW-002), enabling consistent
cross-referencing between the two features. Unicode 3.0 is the historical baseline for
most terminal emulators; Unicode 13.0 introduced the Sextant and other legacy computing
blocks widely used in modern TUI applications; Unicode 16.0 is the latest version
bundled at the time of writing. Storing tables as compile-time constant arrays (Ada
constant array aggregates or equivalent) ensures that the SPARK prover can treat the
table contents as known at proof time and that no heap allocation is required at
runtime, satisfying FUNC-CWM-012.
<<<

[REQUIREMENT]
UID: FUNC-CWM-002
STATUS: Approved
PRIORITY: Must
TITLE: Codepoint Range Entry Format
STATEMENT: >>>
Each entry in a Unicode width table shall be a record with the following fields:

  First : Unicode_Scalar_Value
    -- The first codepoint of this range (inclusive).

  Last  : Unicode_Scalar_Value
    -- The last codepoint of this range (inclusive).
    -- Invariant: Last >= First.

  Width : Cell_Width_Value
    -- The terminal column width assigned to every codepoint in [First .. Last].
    -- Possible values: 0 (combining/non-spacing), 1 (narrow), 2 (wide/fullwidth).

Where:
  Unicode_Scalar_Value is a subtype of Natural covering U+0000 .. U+10FFFF
  (excluding the surrogate range U+D800 .. U+DFFF).

  Cell_Width_Value is an integer subtype with range 0 .. 2.

A codepoint that does not fall within any explicitly listed range shall be treated as
having width 1 (narrow) by the lookup function (FUNC-CWM-002). This default avoids
the need to enumerate every assigned narrow codepoint explicitly and keeps table size
manageable.

The entries within each table shall be stored in ascending order of First, with no
overlapping ranges permitted. These invariants shall be established by construction
(the table generator ensures sorted, non-overlapping output) and may be asserted by
Ghost functions in SPARK-annotated code.
<<<
COMMENT: >>>
Defining a record type for range entries (rather than parallel arrays or a flat
lookup array over all 1,114,112 codepoints) keeps the table compact: the Unicode
standard assigns width 2 to a few thousand CJK codepoints and width 0 to a few
thousand combining marks, but the vast majority of codepoints are width 1 and need
not appear in the table at all if 1 is the default. The sorted, non-overlapping
invariant is required for the binary search algorithm (FUNC-CWM-002) to be correct
and SPARK-provable. Expressing the invariant as a Ghost predicate makes it visible
to GNATprove without runtime overhead.
<<<

[/SECTION]

[SECTION]
TITLE: Binary Search Lookup

[REQUIREMENT]
UID: FUNC-CWM-003
STATUS: Approved
PRIORITY: Must
TITLE: Binary Search Over Sorted Codepoint Ranges
STATEMENT: >>>
The library shall implement a pure function Cell_Width_In_Table that performs binary
search over a sorted array of codepoint range entries (FUNC-CWM-001 and FUNC-CWM-002)
to return the cell width of a given codepoint. A representative signature is:

  function Cell_Width_In_Table
     (Codepoint : Unicode_Scalar_Value;
      Table     : Width_Table)
      return Cell_Width_Value
  with Global => null;

The algorithm shall be:

  1. If Codepoint is in the ASCII fast-path range U+0020 .. U+007E, return 1
     immediately without searching the table (FUNC-CWM-009).

  2. If Codepoint is in the control character range U+0000 .. U+001F or equals
     U+007F, return the control character width defined by FUNC-CWM-011 without
     searching the table.

  3. Set Low := Table'First and High := Table'Last.

  4. While Low <= High:
       Mid := Low + (High - Low) / 2
       If Codepoint < Table (Mid).First then High := Mid - 1
       elsif Codepoint > Table (Mid).Last then Low := Mid + 1
       else return Table (Mid).Width   -- Codepoint is within [First, Last]

  5. If no entry is found, return 1 (the default narrow width).

The function shall carry a loop invariant asserting:
  (a) All entries in Table (Table'First .. Low - 1) have Last < Codepoint.
  (b) All entries in Table (High + 1 .. Table'Last) have First > Codepoint.

These invariants are sufficient for GNATprove to discharge the proof obligations on
the binary search termination and correctness at Gold level.

Cell_Width_In_Table shall be declared with SPARK_Mode => On, Global => null, and
no side effects.
<<<
COMMENT: >>>
Binary search over sorted ranges is O(log N) where N is the number of range entries
in the table. For the Unicode 16.0 table, N is expected to be in the low thousands,
giving approximately 11-12 comparisons per lookup. This satisfies FUNC-CWM-012
(performance) and is vastly more efficient than a flat 1,114,112-element lookup array.
The explicit loop invariant is required for GNATprove to verify the Gold-level
proof obligations (no out-of-bounds access, correct termination). The fast path for
ASCII printable characters (FUNC-CWM-009) and the control character early exit
(FUNC-CWM-011) are placed before the binary search to eliminate table lookups for the
most common inputs in typical terminal output. The default return of 1 for unmatched
codepoints follows the convention used by wcwidth() and by the rich / lipgloss
reference implementations: an unrecognised codepoint is assumed to be a newly assigned
narrow character.
<<<

[/SECTION]

[SECTION]
TITLE: Version Selection

[REQUIREMENT]
UID: FUNC-CWM-004
STATUS: Approved
PRIORITY: Must
TITLE: Table_Version Enumeration
STATEMENT: >>>
The library shall define an enumeration type Table_Version that identifies the
bundled Unicode width table versions. The enumeration shall contain at minimum:

  type Table_Version is
     (Unicode_3,    -- Unicode 3.0 width tables
      Unicode_13,   -- Unicode 13.0 width tables
      Unicode_16);  -- Unicode 16.0 width tables

The enumeration shall be ordered such that Unicode_3 < Unicode_13 < Unicode_16,
reflecting the chronological and monotonically increasing nature of Unicode versions.
This ordering allows callers to compare versions and compute Table_Version'Last to
identify the latest bundled version.

When future Unicode versions are bundled (e.g., Unicode_17), the new value shall be
appended at the end of the enumeration so that Table_Version'Last always designates
the latest available version.

The Table_Version type shall be declared in a SPARK-visible package spec
(SPARK_Mode => On) so that it is usable in contracts and proof obligations.
<<<
COMMENT: >>>
A named enumeration type (rather than a plain integer version number) provides
compile-time exhaustiveness checking: if a new table version is added to the
enumeration but the version-selection case statement (FUNC-CWM-005) is not updated,
the Ada compiler will issue a warning or error about the missing case. This is
superior to integer-keyed dispatch, which would silently fall through to a default
case. The ordering invariant (oldest first, newest last) means Table_Version'Last
is always the correct default version (FUNC-CWM-005).
<<<

[REQUIREMENT]
UID: FUNC-CWM-005
STATUS: Approved
PRIORITY: Must
TITLE: UNICODE_VERSION Environment Variable — Table Selection
STATEMENT: >>>
The library shall read the UNICODE_VERSION environment variable at startup to select
the active Unicode width table version. The selection procedure shall be:

  1. Read the value of UNICODE_VERSION from the process environment.

  2. If UNICODE_VERSION is absent or its value is the empty string, select the
     default version (FUNC-CWM-006) and skip the remaining steps.

  3. Parse the value as a version string. The following formats shall be recognised
     (case-insensitive):

       "3"   or "3.0"   -> Table_Version of Unicode_3
       "13"  or "13.0"  -> Table_Version of Unicode_13
       "16"  or "16.0"  -> Table_Version of Unicode_16

  4. If the parsed version string matches a bundled Table_Version, activate that
     version's table as the process-wide active table.

  5. If the parsed version string does not match any bundled Table_Version (e.g.,
     "14.0" is requested but not bundled), activate the default version
     (FUNC-CWM-006) and record the fact that the requested version was unavailable.
     No exception shall be raised; no diagnostic shall be written to standard output
     or standard error by the library itself.

The active table version shall be determined once at process startup (when the
Cell_Width package is elaborated or when the first Cell_Width call is made) and shall
not change during the lifetime of the process, even if UNICODE_VERSION is subsequently
modified in the environment.

The environment variable read is an I/O operation and shall be performed in a package
body section marked SPARK_Mode => Off. The resulting Table_Version value shall be
stored as a constant and passed to the pure lookup function (FUNC-CWM-003) through a
SPARK-visible constant or function, keeping the lookup path fully SPARK-provable.
<<<
COMMENT: >>>
The UNICODE_VERSION environment variable follows the pattern established by the
reference implementations (rich, lipgloss) and is consistent with the WCWIDTH feature,
which uses the same three versions as sentinel codepoints. Accepting both short ("13")
and long ("13.0") forms reduces friction for users setting the variable manually.
Silently falling back to the default on unrecognised values (rather than raising an
exception) is consistent with Termicap's overall design principle that detection
failures should degrade gracefully. The "determine once at elaboration time" rule
prevents non-deterministic behaviour if the environment is modified after startup, and
allows the SPARK prover to treat the selected version as a constant for proof purposes.
<<<

[REQUIREMENT]
UID: FUNC-CWM-006
STATUS: Approved
PRIORITY: Must
TITLE: Default Version Selection — Latest Bundled Table
STATEMENT: >>>
When the UNICODE_VERSION environment variable is absent, empty, or contains an
unrecognised version string (FUNC-CWM-005), the library shall select the latest
bundled Unicode width table as the active version. The latest bundled version is
defined as Table_Version'Last (FUNC-CWM-004), which is the enumeration value with
the highest ordinal position.

The default version selection shall require no runtime computation: Table_Version'Last
is a static compile-time expression in Ada. No fallback table search or version
negotiation is needed.

The selected default version shall be the same version that would be selected by
setting UNICODE_VERSION to the corresponding version string (e.g., if Table_Version'Last
is Unicode_16, the default is identical to setting UNICODE_VERSION="16.0").

The default version shall be documented in the package specification so that callers
know which table they are using when they do not set UNICODE_VERSION.
<<<
COMMENT: >>>
Defaulting to the latest bundled version is the right choice for a library intended
to handle modern terminal output: newer Unicode tables have more accurate width data
for recently assigned codepoints and emoji, and most users want the most accurate
width measurement available. Users who need to match a specific terminal's Unicode
version (e.g., a terminal still using Unicode 13 character width tables) can set
UNICODE_VERSION explicitly. Using Table_Version'Last as the Ada expression for the
default ensures the documentation stays automatically consistent with the code: when
a new version is added to the enumeration, Table_Version'Last changes to reflect it
without requiring a separate constant update.
<<<

[/SECTION]

[SECTION]
TITLE: Special Codepoint Handling

[REQUIREMENT]
UID: FUNC-CWM-007
STATUS: Approved
PRIORITY: Must
TITLE: ZWJ — Zero Width Joiner Cell Width
STATEMENT: >>>
The library shall return a cell width of 0 for U+200D (ZERO WIDTH JOINER, ZWJ).

ZWJ has Unicode general category Cf (Format character) and is explicitly a zero-width
codepoint: it occupies no terminal columns when rendered in isolation. When ZWJ appears
within an emoji ZWJ sequence (e.g., family emoji U+1F468 U+200D U+1F469 U+200D
U+1F467), the ZWJ itself still contributes 0 columns; the total sequence width is
determined by how the terminal renders the combined glyph, which is outside the scope
of single-codepoint measurement.

The Cell_Width function shall return 0 for U+200D regardless of the active table
version. This value shall be encoded explicitly in each bundled table (as a range
entry [U+200D, U+200D, 0]) or handled as a special case in the lookup function, so
that the binary search returns 0 rather than the default 1.

The requirement that Cell_Width returns 0 for ZWJ itself is the minimal correct
behaviour for single-codepoint measurement. Callers that need to measure multi-codepoint
ZWJ sequences shall sum the widths of all non-ZWJ codepoints in the sequence (the ZWJ
itself contributes 0).
<<<
COMMENT: >>>
ZWJ handling is specified explicitly because it is a commonly mishandled edge case in
terminal width measurement libraries. Returning 0 for ZWJ in isolation is correct per
the Unicode standard (ZWJ is a zero-width format character). The note about ZWJ
sequences is informative rather than normative: sequence-level width measurement
(where the terminal may render a multi-codepoint sequence as a single 2-wide glyph)
is a higher-level concern beyond the scope of this feature's single-codepoint Cell_Width
function. Reference implementations (rich, lipgloss) handle ZWJ sequences at a higher
layer by detecting ZWJ in the sequence and assigning the width of the base character
to the whole sequence.
<<<

[REQUIREMENT]
UID: FUNC-CWM-008
STATUS: Approved
PRIORITY: Must
TITLE: VS16 — Variation Selector-16 Cell Width
STATEMENT: >>>
The library shall return a cell width of 0 for U+FE0F (VARIATION SELECTOR-16, VS16).

VS16 is a variation selector (Unicode general category Mn, non-spacing mark) that,
when it immediately follows an emoji base character, signals that the preceding
character should be rendered as an emoji (typically a 2-wide coloured glyph rather
than a 1-wide text symbol). VS16 itself is a non-spacing, zero-width codepoint and
occupies no terminal columns.

The Cell_Width function shall return 0 for U+FE0F regardless of the active table
version. This value shall be encoded explicitly in each bundled table (as a range
entry [U+FE0F, U+FE0F, 0]) or handled as a special case in the lookup function.

The effect of VS16 on the preceding character's rendered width (upgrading a 1-wide
text symbol to a 2-wide emoji) is a sequence-level concern and is outside the scope
of the single-codepoint Cell_Width function. Callers measuring sequences containing
VS16 shall account for this upgrade at a higher processing layer.
<<<
COMMENT: >>>
VS16 (U+FE0F) is the second most common zero-width codepoint encountered in emoji
sequences after ZWJ. Correctly returning 0 for VS16 is necessary for any library that
measures the display width of modern Unicode text containing emoji. The sequence-level
upgrade effect (text presentation -> emoji presentation) is explicitly excluded from
this feature's scope, consistent with the single-codepoint contract of Cell_Width.
The reference implementations (rich, wcwidth.py, lipgloss) all return 0 for U+FE0F.
<<<

[REQUIREMENT]
UID: FUNC-CWM-009
STATUS: Approved
PRIORITY: Must
TITLE: Combining Characters — General Category M Width
STATEMENT: >>>
The library shall return a cell width of 0 for all codepoints with Unicode general
category M (Mark): Mn (Non-spacing Mark), Mc (Spacing Mark), and Me (Enclosing Mark).

Combining characters in category M are zero-width in the sense that they modify a
preceding base character and do not independently advance the cursor position. Their
cell width is universally 0 on all conforming terminal implementations.

Category M codepoints shall be explicitly encoded in each bundled width table as
ranges with width 0. The table generator shall derive these ranges directly from the
Unicode Character Database (UCD) DerivedGeneralCategory.txt for the corresponding
Unicode version.

The category M ranges shall cover at minimum:
  - U+0300 .. U+036F  (Combining Diacritical Marks)
  - U+1AB0 .. U+1AFF  (Combining Diacritical Marks Extended)
  - U+1DC0 .. U+1DFF  (Combining Diacritical Marks Supplement)
  - U+20D0 .. U+20FF  (Combining Diacritical Marks for Symbols)
  - U+FE20 .. U+FE2F  (Combining Half Marks)
  and all other UCD category-M ranges for the active table version.

The WCWIDTH feature's C library probe (FUNC-WCW-003) can be used to cross-check the
table entries for category-M codepoints: a conforming POSIX wcwidth() should return 0
for all category-M codepoints. Discrepancies indicate either a table error or a
non-conforming locale.
<<<
COMMENT: >>>
Category M is the authoritative Unicode source for combining / non-spacing character
identification. Deriving the table ranges from the UCD (rather than hardcoding them)
ensures correctness and maintainability: when the UCD is updated for a new Unicode
version, re-running the table generator produces the correct updated ranges. The
minimum list of ranges is included as a sanity check, not as an exhaustive enumeration;
the actual table will contain many additional category-M ranges depending on the Unicode
version. The cross-check with WCWIDTH is an informative note for developers validating
the tables, not a runtime dependency.
<<<

[/SECTION]

[SECTION]
TITLE: Fast Paths and Edge Cases

[REQUIREMENT]
UID: FUNC-CWM-010
STATUS: Approved
PRIORITY: Must
TITLE: ASCII Printable Fast Path
STATEMENT: >>>
The Cell_Width function shall implement an explicit fast path for ASCII printable
characters. For any codepoint in the range U+0020 (SPACE) through U+007E (TILDE,
inclusive), the function shall return 1 immediately without performing a binary search
over the width table.

This fast path shall be implemented as the first check in Cell_Width, before any table
version selection or binary search. The check shall be a single comparison:

  if Codepoint in 16#0020# .. 16#007E# then return 1;

The fast path applies regardless of the active table version (FUNC-CWM-005):
ASCII printable characters have had width 1 in every Unicode version since
Unicode 1.0 and this assignment is stable.

The fast path is not merely an optimisation; it is a specification requirement that
ensures Cell_Width behaves correctly for ASCII input even in the event of a table
generation error for the ASCII range.
<<<
COMMENT: >>>
ASCII printable characters (U+0020..U+007E) are the most frequent input to any text
width measurement function in practice: typical terminal output is predominantly ASCII.
Handling them without a table lookup eliminates the dominant case from the binary search
path entirely, improving average-case performance. The rationale for making the fast
path a specification requirement (rather than an implementation detail) is testability
and correctness assurance: a test suite can verify the fast path independently of the
table data. The range U+0020..U+007E is precisely the printable ASCII range; U+0020
(SPACE) is included (width 1, takes one column) and U+007F (DEL) is excluded (handled
by FUNC-CWM-011 as a control character).
<<<

[REQUIREMENT]
UID: FUNC-CWM-011
STATUS: Approved
PRIORITY: Must
TITLE: Control Characters — Width Convention
STATEMENT: >>>
The Cell_Width function shall handle control characters as follows:

  U+0000 .. U+001F  (C0 controls, including NUL, TAB, LF, CR, ESC, etc.)
    Cell_Width returns 0.

  U+007F            (DEL, C0 delete)
    Cell_Width returns 0.

  U+0080 .. U+009F  (C1 controls)
    Cell_Width returns 0.

The rationale for returning 0 (rather than -1) is:

  1. Cell_Width_Value is typed as 0 .. 2 (FUNC-CWM-002); returning -1 would require
     widening the return type to include a sentinel, adding complexity to callers and
     preventing SPARK proof of the range constraint.

  2. Most callers that use Cell_Width for text layout (measuring how many columns a
     string occupies) should treat control characters as zero-width for layout
     purposes: a TAB is typically expanded to spaces by the higher-level layer, and
     NUL / ESC sequences do not contribute to the visible display width.

  3. The POSIX wcwidth() convention of returning -1 for non-printable characters is
     relevant to the WCWIDTH feature (FUNC-WCW-007), not to this feature's static
     table model.

Callers that need to distinguish "control character" from "combining mark" (both of
which return 0 from Cell_Width) may inspect the codepoint range directly. This feature
does not provide a separate Is_Control_Character predicate; such a predicate is outside
scope.

The control character ranges shall be handled by early-exit checks in Cell_Width (before
the binary search), or equivalently by explicit 0-width range entries in each bundled
table. Either implementation is acceptable, provided the return value is 0 for all
control codepoints defined above.
<<<
COMMENT: >>>
The choice of 0 (not -1) for control characters is the central design decision for
this feature. The wcwidth() convention of -1 for non-printable characters is useful in
a C API (where int can hold -1) but is awkward in a strongly-typed Ada API where the
return type is 0 .. 2. Returning 0 for control characters is consistent with the Python
wcwidth library, the Go uniseg library, and with the way terminal layout engines
typically handle control characters (treat them as zero-width and let a higher layer
expand them). The requirement documents this choice explicitly so that consumers of
the Cell_Width API are not surprised by the deviation from POSIX wcwidth() convention.
<<<

[/SECTION]

[SECTION]
TITLE: Public API

[REQUIREMENT]
UID: FUNC-CWM-012
STATUS: Approved
PRIORITY: Must
TITLE: Cell_Width Public Function Specification
STATEMENT: >>>
The library shall expose the cell width measurement feature through the following
public API, declared in a package Termicap.Cell_Width (SPARK_Mode => On):

  -- The terminal column width of a single Unicode codepoint.
  -- 0 = combining/non-spacing/control; 1 = narrow; 2 = wide/fullwidth.
  subtype Cell_Width_Value is Integer range 0 .. 2;

  -- A valid Unicode scalar value: U+0000..U+D7FF and U+E000..U+10FFFF.
  subtype Unicode_Scalar_Value is Natural range 0 .. 16#10_FFFF#;

  -- The active table version, determined once at elaboration time.
  -- Set by UNICODE_VERSION env var; defaults to Table_Version'Last.
  Active_Version : constant Table_Version;

  -- Return the terminal column width for a single Unicode scalar value.
  -- Pure function: no I/O, no side effects, no global reads.
  -- O(log N) binary search over the active table (FUNC-CWM-003).
  -- Fast path for ASCII printable (U+0020..U+007E) returns 1 immediately.
  -- Control characters (U+0000..U+001F, U+007F, U+0080..U+009F) return 0.
  function Cell_Width (Codepoint : Unicode_Scalar_Value) return Cell_Width_Value
  with Global => null;

  -- Return the cell width using an explicitly specified table version.
  -- Useful for callers that need to override the process-wide active version.
  function Cell_Width
     (Codepoint : Unicode_Scalar_Value;
      Version   : Table_Version)
      return Cell_Width_Value
  with Global => null;

Both Cell_Width overloads shall be pure functions (Global => null) with no side
effects, suitable for use in SPARK-annotated code at Gold level.

The package shall not depend on Termicap.Wcwidth or Termicap.Unicode: it is a
standalone measurement utility. Callers that wish to combine Cell_Width with
WCWIDTH probing shall do so at a higher layer in their own code.
<<<
COMMENT: >>>
Two overloads of Cell_Width are provided: the zero-argument version uses the
process-wide active version selected at startup (the common case); the version-explicit
overload allows callers to specify a table version directly, which is useful in tests
and in scenarios where the caller manages version selection independently of the
environment variable. Both overloads are pure and SPARK-provable. Active_Version is
exported as a constant so that callers can log or display the active version without
calling a function. The standalone design (no dependency on Termicap.Wcwidth or
Termicap.Unicode) keeps the package reusable in contexts where only cell width
measurement is needed without the full Termicap detection stack.
<<<

[/SECTION]

[SECTION]
TITLE: Integration with WCWIDTH Feature

[REQUIREMENT]
UID: FUNC-CWM-013
STATUS: Approved
PRIORITY: Should
TITLE: Complementary Use with WCWIDTH Probing
STATEMENT: >>>
The Cell_Width function (FUNC-CWM-012) and the WCWIDTH probe (wcwidth.sdoc,
FUNC-WCW-003) address the same problem domain — determining the terminal column count
for a Unicode codepoint — through different mechanisms:

  Cell_Width  : static table lookup; O(log N); no OS calls; SPARK Gold; consistent
                across platforms and locales; table version is UNICODE_VERSION-controlled.

  wcwidth()   : runtime C library call; depends on locale initialisation; reports the
                OS's view of the current locale's Unicode coverage; may differ from
                Cell_Width if the locale uses an older Unicode version than the active
                table.

The library shall document the following integration pattern for callers that wish to
use both features:

  Step 1. Call Termicap.Wcwidth.Probe_Wcwidth_Level to determine the Unicode version
          supported by the OS locale (FUNC-WCW-003).

  Step 2. Convert the Wcwidth_Level to a Table_Version using the mapping:
            Unknown    -> use Active_Version (FUNC-CWM-006 default)
            Unicode_3  -> Table_Version of Unicode_3
            Unicode_13 -> Table_Version of Unicode_13
            Unicode_16 -> Table_Version of Unicode_16

  Step 3. Call Cell_Width (Codepoint, Resolved_Version) to measure codepoint width
          using the table that matches the OS locale's actual Unicode coverage.

This integration pattern is advisory (a Should, not a Must) because many callers
will prefer using only Cell_Width with the default table (simplest and most accurate
for modern terminals) or only wcwidth() (when POSIX locale fidelity is required).

The Termicap.Cell_Width package shall not depend on Termicap.Wcwidth at the package
level. The integration pattern shall be documented in the package specification comment
only, not enforced by package structure.
<<<
COMMENT: >>>
The integration pattern is specified here (rather than in the WCWIDTH feature document)
because it describes how to use the WCWIDTH probe result to select the Cell_Width table
version. The "Should" priority reflects that this is a useful combination but not a
required one: the most common use case is Cell_Width with the default table, which
works correctly for modern terminals without any WCWIDTH probe. The mapping from
Wcwidth_Level to Table_Version is straightforward because both hierarchies use the
same three Unicode versions (3.0, 13.0, 16.0) as their reference points, by design.
<<<

[/SECTION]

[SECTION]
TITLE: SPARK Provability

[REQUIREMENT]
UID: FUNC-CWM-014
STATUS: Approved
PRIORITY: Must
TITLE: SPARK Gold Provability — Pure Lookup and Arithmetic
STATEMENT: >>>
The Cell_Width lookup functions (both overloads, FUNC-CWM-012) and the binary search
algorithm (FUNC-CWM-003) shall be SPARK-provable at Gold level. The following
properties shall be established by GNATprove without manual lemmas or pragma Assume:

  1. No array out-of-bounds access: the binary search loop accesses only valid indices
     within the table array. Established by the loop invariants defined in FUNC-CWM-003.

  2. No integer overflow: all arithmetic in the binary search (Low, High, Mid
     computations) is performed within Natural or a bounded integer subtype. Mid is
     computed as Low + (High - Low) / 2 to avoid overflow when Low and High are large.

  3. Return value in range: Cell_Width always returns a value in Cell_Width_Value
     (0 .. 2). Established by the fact that all table entries have Width in 0 .. 2,
     the fast path returns 1 (in range), and the default return is 1 (in range).

  4. Termination: the binary search loop terminates because High - Low strictly
     decreases on every iteration. This shall be expressed as a loop variant.

  5. Global => null: Cell_Width reads only its Codepoint and Version arguments and
     the compile-time constant table arrays; it reads no package-level variables,
     performs no I/O, and raises no exceptions.

The package body's elaboration code that reads UNICODE_VERSION (FUNC-CWM-005) shall
be declared with SPARK_Mode => Off, isolating the non-provable I/O from the provable
lookup path. The Active_Version constant (FUNC-CWM-012) shall be populated by the Off
section and exposed as a constant to the On section, so that Cell_Width (Codepoint)
(the single-argument overload) can be verified as a pure wrapper around Cell_Width
(Codepoint, Active_Version) without any global reads.
<<<
COMMENT: >>>
Gold-level SPARK provability for Cell_Width is achievable because the function is a
pure mathematical operation on bounded integer inputs and constant array data: there
are no pointers, no heap allocation, no recursion, no exceptions, and no I/O. The key
proof obligations are array bounds (handled by loop invariants) and return range
(handled by table entry type constraints). The overflow-safe mid computation
(Low + (High - Low) / 2 rather than (Low + High) / 2) is a standard technique
required here because Low and High are indices into a potentially large array. The
Active_Version isolation (Off for env var read, On for lookup) follows the same SPARK
boundary pattern used throughout Termicap (TTY detection, WCWIDTH, OSC Query).
<<<

[/SECTION]

[SECTION]
TITLE: Performance

[REQUIREMENT]
UID: FUNC-CWM-015
STATUS: Approved
PRIORITY: Must
TITLE: O(log N) Lookup and Constant Table Storage
STATEMENT: >>>
The Cell_Width lookup shall satisfy the following performance constraints:

  Time complexity: O(log N) per call, where N is the number of range entries in the
  active width table. For the Unicode 16.0 table (expected N < 2 000), this yields
  at most ceil(log2(2000)) = 11 comparisons per lookup after the fast-path checks.

  Space complexity: O(N) total for all bundled tables combined, stored as compile-time
  constant arrays in the library's read-only data segment. No heap allocation shall
  occur at any point in the Cell_Width call path.

  Startup cost: the UNICODE_VERSION environment variable is read exactly once, at
  package elaboration time. All subsequent calls to Cell_Width incur no environment
  variable reads, no system calls, and no locking.

  Table access pattern: the binary search accesses at most ceil(log2(N)) + 1 table
  entries per call, each being a record read from a constant array. Modern CPUs will
  cache the active table in L1/L2 for repeated calls, making the practical latency
  significantly lower than the worst-case comparison count suggests.

These constraints shall be documented in the package specification so that callers can
reason about the cost of Cell_Width in hot paths (e.g., measuring every character of
a large terminal output buffer).
<<<
COMMENT: >>>
The O(log N) binary search over precomputed ranges is the standard approach used by
the reference implementations (rich, wcwidth.py, uniseg) and is well established as
the correct time/space trade-off for Unicode width tables. A flat O(1) array covering
all 1,114,112 codepoints would be faster but would consume approximately 1 MB of
memory (one byte per codepoint), which is unacceptable for a lightweight terminal
capability library. The expected table size of under 2,000 entries (based on analysis
of the Unicode 16.0 width data) means the table fits comfortably in a typical CPU
cache line set, making the practical performance close to O(1) for repeated queries
against the same codepoint range.
<<<

[/SECTION]

[SECTION]
TITLE: Testing

[REQUIREMENT]
UID: FUNC-CWM-016
STATUS: Approved
PRIORITY: Should
TITLE: Test Coverage for Cell Width Lookup
STATEMENT: >>>
The test suite shall include tests verifying the behaviour of Cell_Width for the
following categories of input, across all bundled table versions:

  1. ASCII fast path (FUNC-CWM-010):
       Cell_Width (16#0020#) = 1  (SPACE)
       Cell_Width (16#0041#) = 1  (LATIN CAPITAL LETTER A)
       Cell_Width (16#007E#) = 1  (TILDE)

  2. Control characters (FUNC-CWM-011):
       Cell_Width (16#0000#) = 0  (NUL)
       Cell_Width (16#000A#) = 0  (LINE FEED)
       Cell_Width (16#001F#) = 0  (UNIT SEPARATOR)
       Cell_Width (16#007F#) = 0  (DEL)
       Cell_Width (16#0080#) = 0  (PAD, C1 control)
       Cell_Width (16#009F#) = 0  (APPLICATION PROGRAM COMMAND)

  3. ZWJ (FUNC-CWM-007):
       Cell_Width (16#200D#) = 0

  4. VS16 (FUNC-CWM-008):
       Cell_Width (16#FE0F#) = 0

  5. Combining characters (FUNC-CWM-009):
       Cell_Width (16#0300#) = 0  (COMBINING GRAVE ACCENT)
       Cell_Width (16#036F#) = 0  (COMBINING LATIN SMALL LETTER X)
       Cell_Width (16#20D0#) = 0  (COMBINING LEFT HARPOON ABOVE)

  6. Wide / fullwidth characters:
       Cell_Width (16#4E00#) = 2  (CJK UNIFIED IDEOGRAPH-4E00)
       Cell_Width (16#FF01#) = 2  (FULLWIDTH EXCLAMATION MARK)
       Cell_Width (16#1F600#) = 2 (GRINNING FACE emoji)

  7. Narrow non-ASCII characters:
       Cell_Width (16#00E9#) = 1  (LATIN SMALL LETTER E WITH ACUTE)
       Cell_Width (16#03B1#) = 1  (GREEK SMALL LETTER ALPHA)

  8. Version-specific codepoints (table version boundary check):
       With Unicode_3  table: Cell_Width (16#28FF#) = 1 (BRAILLE PATTERN DOTS-12345678)
       With Unicode_13 table: Cell_Width (16#1FB38#) = 1 (UPPER LEFT BLOCK SEXTANT)
       With Unicode_16 table: Cell_Width (16#1CD00#) = 1 (SIGNWRITING HAND codepoint)

  9. Binary search edge cases:
       First entry in the table: correct width returned.
       Last entry in the table: correct width returned.
       Codepoint not in any range: returns 1 (default narrow).

  10. UNICODE_VERSION parsing (FUNC-CWM-005):
       "3" and "3.0" both select Table_Version of Unicode_3.
       "13" and "13.0" both select Table_Version of Unicode_13.
       "16" and "16.0" both select Table_Version of Unicode_16.
       Unrecognised value (e.g., "99.0") selects Table_Version'Last (FUNC-CWM-006).
       Empty string selects Table_Version'Last (FUNC-CWM-006).
<<<
COMMENT: >>>
The test cases are grouped by the requirement they exercise, enabling traceability
between the test suite and this requirements document. The version-specific codepoints
in category 8 reuse the WCWIDTH sentinel codepoints (FUNC-WCW-002) so that the two
features can be cross-validated: a codepoint that the WCWIDTH probe detects as valid
(width >= 1) should also return width 1 from Cell_Width in the corresponding table
version. The binary search edge cases in category 9 are important for correctness
proof: the first and last entries exercise the boundary conditions that the loop
invariants must cover. The UNICODE_VERSION parsing tests in category 10 are best
implemented as unit tests with controlled environment variable injection so that they
do not depend on the actual process environment.
<<<

[/SECTION]
