[DOCUMENT]
TITLE: Non-Functional Requirements
UID: REQ-NFR

[GRAMMAR]
ELEMENTS:
- TAG: REQUIREMENT
  FIELDS:
  - TITLE: UID
    TYPE: String
    REQUIRED: True
  - TITLE: STATUS
    TYPE: SingleChoice(Draft, Approved, In Progress, Implemented, Verified)
    REQUIRED: False
  - TITLE: PRIORITY
    TYPE: SingleChoice(Must, Should, Could, Wont)
    REQUIRED: False
  - TITLE: GITHUB
    TYPE: String
    REQUIRED: False
  - TITLE: TITLE
    TYPE: String
    REQUIRED: False
  - TITLE: STATEMENT
    TYPE: String
    REQUIRED: True
  - TITLE: COMMENT
    TYPE: String
    REQUIRED: False
  RELATIONS:
  - TYPE: Parent
